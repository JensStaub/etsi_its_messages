MCM-PDU-Descriptions {
	itu-t (0) identified-organization (4) etsi (0) itsDomain (5) wg1 (1) ts(103561) mcm (1) major-version-1 (1) minor-version-1 (1)
}



DEFINITIONS AUTOMATIC TAGS ::=

BEGIN

IMPORTS

--@brief Include ETSI TS 102 894-2

GenerationDeltaTime, Identifier1B, Iso3833VehicleType, ItsPduHeader, ReferencePosition, SpecialTransportType, Speed, StationId, VehicleHeight,
VehicleLength, VehicleWidth, Wgs84Angle

FROM ETSI-ITS-CDD {itu-t (0) identified-organization (4) etsi (0) itsDomain (5) wg1 (1) 102894 cdd (2) major-version-4 (4) minor-version-2 (2)};



-- Manoeuvre Coordination Block:

/**
 * This type represents the Manoeuvre Coordination Block at a given facility.
 *
 * It shall include the following components:
 *
 * @field header: the header of the MCM PDU,
 *
 * @field mcm: the payload of the MCM PDU,
*/

MCM ::= SEQUENCE {
	header	ItsPduHeader,
	payload	McmBasicContainer
}

McmBasicContainer ::= SEQUENCE {
	generationDeltaTime GenerationDeltaTime,
	stationType McmStationType, -- Type of originating ITS-S (VRU Portable Device, vehicle (vehicle type) or roadside unit or central station)
	itssRole McmItssRole, -- The role of the originating ITS-S can only be identified once the MC is accepted by all relevant participants
	position ReferencePosition, -- Time relative delta of the latest WGS84 geographic position of the originating ITS-S as obtained by the MCS at the time of MCM generation (only for vehicle ITS-S)
	mcmData McmContainer
}

McmStationType ::= ENUMERATED {
	vruPortableDevice (0),
	vehicle (1),
	roadsideUnit (2),
	centralStation (3),
	...
}

McmItssRole ::= ENUMERATED {
	notAvailable (0),
	coordinatingItss (1),
	notCoordinatingSubjectVehicle (2),
	targetVehicle (3),
	...
}

McmContainer ::= CHOICE {
	vehicleManoeuvreContainer VehicleManoeuvreContainer,
	advisedManoeuvreContainer ManoeuvreAdviceContainer
}

VehicleManoeuvreContainer::= SEQUENCE {
	mcmGenericCurrentStateContainer McmGenericCurentStateContainer,
	vehicleCurrentStateContainer VehicleCurrentStateContainer, -- Specific state of the vehicle for an ITS-S of the type vehicle or of the type VRU portable device
	submaneuvres ListOfSubmanoeuvreDescriptionsContainer,
	manoeuvreAdvice  ManoeuvreAdviceContainer OPTIONAL -- sending advice to target vehicles
}

McmGenericCurentStateContainer::= SEQUENCE {
	mcmType McmType, -- type of manoeuvre coordination message
	manoeuvreId ManoeuvreId, -- MCS session ID (its-s ID provided in header and integer modulo 256)
	concept ManoeuvreCoordinationConcept,
	rational ManoeuvreCoordinationRational OPTIONAL, -- Rational to be associated to an offer, intent, advice or a request. Depending on the manoeuvre coordination concept being used.
													 -- For agreement seeking concept the cooperationCost rational can be provided (optional),
													 -- while for the prescriptive concept, the cooperationGoal rational shall be provided
	executionStatus ManoeuvreExecutionStatus OPTIONAL -- Only present in MCM type 7 and type 4
}

VehicleCurrentStateContainer::= SEQUENCE {
	manoeuvreOverallStrategy ManoeuvreOverallStrategy,
	vehicleSpeed Speed,
	vehicleHeading Wgs84Angle,
	vehicleSize VehicleSize
}

ManoeuvreOverallStrategy::= CHOICE {
	undefined NULL,
	transitToHumanDrivenMode NULL,
	transitToAutomatedDrivingMode NULL,
	driveStraight NULL,
	turnLeft NULL,
	turnRight NULL,
	uTurn NULL,
	moveBackward NULL,
	overtake NULL,
	accelerate NULL,
	slowdown NULL,
	stop NULL,
	goToLeftLane NULL,
	oToRightLane NULL,
	getOnHighway NULL,
	exitHighway NULL,
	takeTollingLane INTEGER (1..31), -- laneNumber
	stopAndWait NULL,
	emergencyBrakeAndStop NULL,
	resetStopAndRestartMoving NULL,
	stayInLane NULL,
	resetStayInLane NULL,
	stayAway NULL,
	resetStayAway NULL,
	followMe NULL,
	existingGroup NULL,
	temporarilyDisbandAnExistingGroup NULL,
	constituteAtemporarilyGroup NULL,
	disbandATemporarilyGroup NULL
}

ListOfSubmanoeuvreDescriptionsContainer::= SEQUENCE (SIZE(0..31)) OF SubmanoeuvreDescription

SubmanoeuvreDescription::= SEQUENCE {
	submanoeuvreID Identifier1B, -- Unique ID of the sub manoeuvre
	submanoeuvreStrategy SubmanoeuvreStrategy OPTIONAL,
	referenceTrajectory Trajectory OPTIONAL,
	targetRoadResourceIContainer TrrDescription OPTIONAL, -- Type 3 is selected when reference trajectory is used
	temporalCharateristics TemporalCharacteristics,
	kinematicsCharacteristics KinematicsCharacteristics
}

McmType::= ENUMERATED {
	intent (0),
	request (1),
	response (2),
	reservation (3),
	termination (4),
	cancellationRequest (5),
	emergencyManoeuvreReservation (6),
	executionStatus (7),
	offer (8)
}

ManoeuvreId::= Identifier1B

ManoeuvreCoordinationConcept ::= ENUMERATED {
	agreementSeeking (0),
	prescriptive (1)
}

ManoeuvreCoordinationRational ::= CHOICE {
	manoeuvreCooperationGoal ManoeuvreCooperationGoal, 	-- Only in case of prescriptive concept
	manoeuvreCooperationCost ManoeuvreCooperationCost	-- Only in case of agreement seeking
}

ManoeuvreCooperationGoal ::= ENUMERATED {
	vehicleInterception (0),
	roadSafety (1),
	humanHelth (2),
	emergencyIntervention (3),
	roadOperatorIntervention (4),
	localTrafficManagement (5),
	globalTrafficManagement (6)
}

ManoeuvreCooperationCost ::= INTEGER {
	zero(0),
	oneThousndth(1)
} (-1000..1000) -- Only in case of agreement seeking


ManoeuvreExecutionStatus ::= ENUMERATED { -- Only for MCM of type 4 and type 7
	started (0),
	inProgress (1),
	completed (2),
	terminated (3),
	chained (4)
}

SubmanoeuvreStrategy::= CHOICE {
	undefined NULL,
	transitToHumanDrivenMode NULL,
	transitToAutomatedDrivingMode NULL,
	driveStraight NULL,
	turnLeft NULL,
	turnRight NULL,
	uTurn NULL,
	moveBackward NULL,
	overtake NULL,
	accelerate NULL,
	slowDown NULL,
	stop NULL,
	goToLeftLane NULL,
	goToRightLane NULL,
	getOnHighway NULL,
	exitHighway NULL,
	takeTollingLane INTEGER (1..31), -- laneNumber
	stopAndWait NULL,
	emergencyBrakeAndStop NULL,
	resetStopAndRestartMoving NULL,
	stayInLane NULL,
	resetStayInLane NULL,
	stayAway NULL,
	resetStayAway NULL,
	followMe NULL,
	existingGroup NULL,
	temporarilyDisbandAnExistingGroup NULL,
	constituteATemporarilyGroup NULL,
	disbandATemporarilyGroup NULL
}

VehicleSize::= SEQUENCE {
	vehicleType Iso3833VehicleType,
	vehicleTransportedGoods SpecialTransportType OPTIONAL, -- ??
	vehicleLenth VehicleLength,
	vehicleWidth VehicleWidth,
	vehicleHeight VehicleHeight
}

Trajectory::= SEQUENCE {
	wayPointType WayPointType,
	wayPoints SEQUENCE (SIZE (1..10)) OF WayPoint, -- Including starting way point and ending way point
	longitudePositions SEQUENCE (SIZE (1..10)) OF LongitudePosition,
	latitudePositions SEQUENCE (SIZE (1..10)) OF LatitudePosition,
	altitudePositions SEQUENCE (SIZE (1..10)) OF AltitudePosition OPTIONAL,
	headings SEQUENCE (SIZE (1..11)) OF Wgs84Angle OPTIONAL,
	speed INTEGER (0..511) -- in meters per second
}

WayPointType ::= ENUMERATED {
	startingWayPoint (0),
	intermediateWayPoint (1),
	endingWayPoint (2)
}

LongitudePosition ::= NULL

LatitudePosition ::= NULL

AltitudePosition ::= NULL

WayPoint ::= NULL

ManoeuvreAdviceContainer::= SEQUENCE (SIZE(1..16)) OF ManoeuvreAdvice

ManoeuvreAdvice ::= SEQUENCE {
	executantID StationId,
	currentStateAdvisedChange CurrentStateAdvisedChange,
	submaneuvres Submanoeuvres
}

Submanoeuvres ::= SEQUENCE (SIZE(1..16)) OF Submanoeuvre

Submanoeuvre ::= SEQUENCE {
	submanoeuvreId Identifier1B,
	advisedTrajectory Trajectory OPTIONAL,
	advisedTargetRoadResource AdvisedTrrContainer OPTIONAL
}

AdvisedTrrContainer::= SEQUENCE {
	trrDescription TrrDescription,
	temporalCharacteristics TemporalCharacteristics,
	kinematicsCharacteristics KinematicsCharacteristics
}

TrrDescription ::= SEQUENCE {
	trrType TrrType,
	laneCount LaneCount, -- Number of adjacent lanes covered by the TRR surface from the starting lane number with a relavive position for each one
	startingLaneNumber LaneCount OPTIONAL, --: identification of the lane in which the executant vehicle starts the submanoeuvre
	endingLaneNumber LaneCount OPTIONAL, -- Identification of the lane in which the executant vehicle ends the submanoeuvre
	waypoints SEQUENCE (SIZE (2..16)) OF WayPoint OPTIONAL, -- At least the starting and ending waypoints used to specify the length of the covered TRR. Optional intermediary waypoints can be added
	heading SEQUENCE (SIZE (2..16)) OF Wgs84Angle OPTIONAL, -- At the level of all identified waypoints
	trrWidth TRRWidth, -- computed from the lane count
	trrLength TRRLength -- computed distance between the starting and ending waypoints
}

TrrType ::= ENUMERATED {
	trrType1(0),
	trrType2(1),
	trrType3(2)
}

LaneCount::= INTEGER (0..31) -- (1+RLLC+RRLC): Can be used to obtain the TRR surface width or just identifying the lanes which belong to the reserved TRR

RLLC ::= BIT STRING {  -- Required Left Lanes Count
    currentLane (0)
} (SIZE (8))

RRLC ::= BIT STRING {  -- Required Right Lanes Count
    currentLane (0)
} (SIZE (8))

TRRWidth ::= INTEGER (0..15) -- LSB units are the width of a lane

TRRLength ::= INTEGER (0..4095) -- LSB units are 0.1 meters: The TRRLength includes safety gaps to be maintained with surrounding vehicles

TemporalCharacteristics::= SEQUENCE {
	tRROccupancyStartTime INTEGER (0..65535), -- LSB unit 1 millisecond: Delta time since the TimesStampIts
	tRROccupancyEndTime INTEGER (0..65535) -- LSB unit 1 millisecond: Delta time since the TimesStampIts
}

KinematicsCharacteristics ::= NULL

CurrentStateAdvisedChange::= CHOICE {
	transitToHumanDrivingMode NULL,
	transitToAutomatedDrivingMode NULL,
	followMeWithMinTimeInterDistance INTEGER (300..2000), -- in Milliseconds
	joinGroup JoinGroupStateChange,
	leaveGroup NULL,
	emergencyBrakeTriggering NULL,
	stayInLane NULL,
	stop NULL,
	resetStop NULL,
	resetStayInLane NULL,
	stayAwayOfVehicleSithStationID NULL,
	resetStayAwayOfVehicle NULL
}

JoinGroupStateChange ::= CHOICE {
	vehicleSynchronization NULL,
	modeLong NULL,
	modeLatLeftLane NULL,
	modeLatRightLane NULL,
	withMinTimeInterDistance INTEGER (300..2000) -- in milliseconds
}

ManouevreResponse::= CHOICE {
	offerAcceptation NULL,
	offerDecline NULL,
	requestAcceptation NULL,
	requestDecline RequestDeclineReaseon
}

RequestDeclineReaseon ::= ENUMERATED {
	agreementSeekingUnknown(0),
	allUnableToConform (1),
	agreementSeekingUnwanted (2),
	allUnableToUnderstand (3),
	allErroneousBehaviourDetected (4),
	allMissbehaviourDetected (5)
}

END
